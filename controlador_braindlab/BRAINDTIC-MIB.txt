BRAINDTIC-MIB DEFINITIONS ::= BEGIN

-- MIB de los equipos BraindTIC. Hoy contiene controlador_braindlab
-- (main/snmp_braindlab.c). Cargar este archivo en el gestor SNMP para ver
-- nombres en vez de OIDs.
--
--   braindtic                     raiz de la empresa
--   braindtic.1                   productos
--   braindtic.1.1                 controlador_braindlab (este archivo)
--   braindtic.1.2 ...             reservados para otros equipos
--   braindtic.2                   reservado: objetos comunes a todos los equipos
--
-- controlador_braindlab (braindlabControlador):
--   .0  notificaciones (traps SNMPv2c)
--   .1  bdlControlTabla   aires acondicionados AA1..AA4 (una fila por aire)
--   .2  bdlSensorTabla    sensores 1..6, temperatura y humedad
--   .3  bdlEnergiaTabla   medidor de energia, fases R, S, T
--   .4  bdlSistema        estado, mando, configuracion y destinos de trap
--   .5  bdlAlarmas        alarmas vigentes (0/1), para polling
--
-- DEMO: braindtic cuelga hoy del "netSnmpPlaypen" de Net-SNMP
-- (1.3.6.1.4.1.8072.9999.9999), rama reservada para pruebas. Cuando IANA
-- asigne el Private Enterprise Number (PEN) de BraindTIC, cambiar SOLO el
-- ::= de braindtic por { enterprises <PEN> } (y OID_BRAINDTIC en
-- snmp_braindlab.c). El resto del arbol no cambia.
--
-- Los objetos read-write responden noAccess mientras no se habilite
-- "Permitir control por SNMP" en la web del equipo (apagado de fabrica).
--
-- SNMP no tiene decimales: temperatura y humedad van en DECIMAS
-- (253 = 25.3 grados C / 25.3 %), voltaje en decimas de V (2205 = 220.5 V)
-- y corriente en centesimas de A (1234 = 12.34 A).

IMPORTS
    MODULE-IDENTITY, OBJECT-TYPE, NOTIFICATION-TYPE,
    Integer32, IpAddress, enterprises
        FROM SNMPv2-SMI
    DisplayString
        FROM SNMPv2-TC;

braindtic MODULE-IDENTITY
    LAST-UPDATED "202610120000Z"
    ORGANIZATION "BraindTIC"
    CONTACT-INFO "BraindTIC"
    DESCRIPTION
        "Raiz de los equipos BraindTIC."
    REVISION     "202610120000Z"
    DESCRIPTION
        "Arbol reorganizado en bloques: control (AA1..AA4), sensores
         (1..6, temperatura y humedad) y energia (fases R, S, T) como
         tablas; estado, mando, configuracion y destinos de trap bajo
         sistema. Agrega el medidor de energia y el trap de prueba."
    REVISION     "202609230000Z"
    DESCRIPTION  "Version inicial (rama demo, sin PEN todavia)."
    ::= { enterprises 8072 9999 9999 }

bdtProductos OBJECT IDENTIFIER ::= { braindtic 1 }

-- ---------------------------------------------------------------------
-- controlador_braindlab
-- ---------------------------------------------------------------------

braindlabControlador OBJECT IDENTIFIER ::= { bdtProductos 1 }

bdlNotificaciones OBJECT IDENTIFIER ::= { braindlabControlador 0 }
bdlSistema        OBJECT IDENTIFIER ::= { braindlabControlador 4 }
bdlAlarmas        OBJECT IDENTIFIER ::= { braindlabControlador 5 }

bdlEstado         OBJECT IDENTIFIER ::= { bdlSistema 1 }
bdlMando          OBJECT IDENTIFIER ::= { bdlSistema 2 }
bdlConfiguracion  OBJECT IDENTIFIER ::= { bdlSistema 3 }
bdlTraps          OBJECT IDENTIFIER ::= { bdlSistema 4 }

-- =====================================================================
-- .1 control -- aires acondicionados AA1..AA4
-- =====================================================================

bdlControlTabla OBJECT-TYPE
    SYNTAX      SEQUENCE OF BdlControlEntrada
    MAX-ACCESS  not-accessible
    STATUS      current
    DESCRIPTION
        "Una fila por aire acondicionado (AA1..AA4). Las 4 filas existen
         siempre; bdlControlInstalado dice cuales maneja el equipo."
    ::= { braindlabControlador 1 }

bdlControlEntrada OBJECT-TYPE
    SYNTAX      BdlControlEntrada
    MAX-ACCESS  not-accessible
    STATUS      current
    DESCRIPTION "Un aire acondicionado."
    INDEX       { bdlControlIndice }
    ::= { bdlControlTabla 1 }

BdlControlEntrada ::= SEQUENCE {
    bdlControlIndice     Integer32,
    bdlControlNombre     DisplayString,
    bdlControlInstalado  INTEGER,
    bdlControlEstado     INTEGER,
    bdlControlModo       INTEGER,
    bdlControlReserva    INTEGER,
    bdlControlFallas     Integer32
}

bdlControlIndice OBJECT-TYPE
    SYNTAX      Integer32 (1..4)
    MAX-ACCESS  not-accessible
    STATUS      current
    DESCRIPTION "Numero de aire: 1 = AA1 ... 4 = AA4."
    ::= { bdlControlEntrada 1 }

bdlControlNombre OBJECT-TYPE
    SYNTAX      DisplayString (SIZE (0..32))
    MAX-ACCESS  read-only
    STATUS      current
    DESCRIPTION
        "Nombre del aire en este sitio (Configuracion > Sitio). Por
         defecto AA1..AA4."
    ::= { bdlControlEntrada 2 }

bdlControlInstalado OBJECT-TYPE
    SYNTAX      INTEGER { no(0), si(1) }
    MAX-ACCESS  read-only
    STATUS      current
    DESCRIPTION "si = el aire esta dentro de la cantidad configurada."
    ::= { bdlControlEntrada 3 }

bdlControlEstado OBJECT-TYPE
    SYNTAX      INTEGER { apagado(0), encendido(1) }
    MAX-ACCESS  read-write
    STATUS      current
    DESCRIPTION
        "GET: rele REALMENTE aplicado (automatico + manual). SET: fuerza
         el aire a mano (= POST /control_aire); dura hasta que la
         climatizacion cambie de etapa o hasta escribir
         bdlModoManual = automatico. En un aire no instalado devuelve
         inconsistentValue."
    ::= { bdlControlEntrada 4 }

bdlControlModo OBJECT-TYPE
    SYNTAX      INTEGER { automatico(0), manual(1) }
    MAX-ACCESS  read-only
    STATUS      current
    DESCRIPTION "manual = este aire tiene un override vigente."
    ::= { bdlControlEntrada 5 }

bdlControlReserva OBJECT-TYPE
    SYNTAX      INTEGER { no(0), si(1) }
    MAX-ACCESS  read-only
    STATUS      current
    DESCRIPTION
        "si = es el aire que descansa esta semana (solo entra en alta
         temperatura). Rota cada lunes a martes."
    ::= { bdlControlEntrada 6 }

bdlControlFallas OBJECT-TYPE
    SYNTAX      Integer32 (0..255)
    MAX-ACCESS  read-only
    STATUS      current
    DESCRIPTION
        "Veces que se llego a alta temperatura mientras este aire era la
         reserva (desde el ultimo arranque)."
    ::= { bdlControlEntrada 7 }

-- =====================================================================
-- .2 sensores -- 1..6, cada uno con temperatura y humedad
-- =====================================================================

bdlSensorTabla OBJECT-TYPE
    SYNTAX      SEQUENCE OF BdlSensorEntrada
    MAX-ACCESS  not-accessible
    STATUS      current
    DESCRIPTION
        "Una fila por sensor (1..6). Hoy: 1..4 = NTC de temperatura
         (Operacion 1, Operacion 2, Inyeccion 1, Inyeccion 2),
         5 = gabinete (temperatura + humedad), 6 = libre. Lo que un
         sensor no mide (ver bdlSensorTipo) vale 0."
    ::= { braindlabControlador 2 }

bdlSensorEntrada OBJECT-TYPE
    SYNTAX      BdlSensorEntrada
    MAX-ACCESS  not-accessible
    STATUS      current
    DESCRIPTION "Un sensor."
    INDEX       { bdlSensorIndice }
    ::= { bdlSensorTabla 1 }

BdlSensorEntrada ::= SEQUENCE {
    bdlSensorIndice              Integer32,
    bdlSensorNombre              DisplayString,
    bdlSensorTipo                INTEGER,
    bdlSensorEstado              INTEGER,
    bdlSensorTemperatura         Integer32,
    bdlSensorHumedad             Integer32,
    bdlSensorCalibTemperatura    Integer32,
    bdlSensorCalibHumedad        Integer32,
    bdlSensorReferenciaTemp      Integer32,
    bdlSensorReferenciaHumedad   Integer32
}

bdlSensorIndice OBJECT-TYPE
    SYNTAX      Integer32 (1..6)
    MAX-ACCESS  not-accessible
    STATUS      current
    DESCRIPTION "Numero de sensor."
    ::= { bdlSensorEntrada 1 }

bdlSensorNombre OBJECT-TYPE
    SYNTAX      DisplayString (SIZE (0..32))
    MAX-ACCESS  read-only
    STATUS      current
    DESCRIPTION
        "Nombre del sensor en este sitio (Configuracion > Sitio), el mismo
         que muestra el panel web."
    ::= { bdlSensorEntrada 2 }

bdlSensorTipo OBJECT-TYPE
    SYNTAX      INTEGER { noInstalado(0), temperatura(1), temperaturaHumedad(2) }
    MAX-ACCESS  read-only
    STATUS      current
    DESCRIPTION "Que mide el sensor."
    ::= { bdlSensorEntrada 3 }

bdlSensorEstado OBJECT-TYPE
    SYNTAX      INTEGER { noInstalado(0), ok(1), falla(2) }
    MAX-ACCESS  read-only
    STATUS      current
    DESCRIPTION
        "falla = no se pudo leer en la ultima vuelta (desconectado, en
         corto o sin respuesta). Mientras falla, los valores son el
         ultimo bueno y el sensor no cuenta para el control."
    ::= { bdlSensorEntrada 4 }

bdlSensorTemperatura OBJECT-TYPE
    SYNTAX      Integer32
    UNITS       "decimas de grado C"
    MAX-ACCESS  read-only
    STATUS      current
    DESCRIPTION "Temperatura calibrada (253 = 25.3 grados C)."
    ::= { bdlSensorEntrada 5 }

bdlSensorHumedad OBJECT-TYPE
    SYNTAX      Integer32 (0..1000)
    UNITS       "decimas de %"
    MAX-ACCESS  read-only
    STATUS      current
    DESCRIPTION "Humedad relativa calibrada (655 = 65.5 %). 0 si no mide humedad."
    ::= { bdlSensorEntrada 6 }

bdlSensorCalibTemperatura OBJECT-TYPE
    SYNTAX      Integer32
    UNITS       "decimas de grado C"
    MAX-ACCESS  read-only
    STATUS      current
    DESCRIPTION "Constante de calibracion vigente de la temperatura."
    ::= { bdlSensorEntrada 7 }

bdlSensorCalibHumedad OBJECT-TYPE
    SYNTAX      Integer32
    UNITS       "decimas de %"
    MAX-ACCESS  read-only
    STATUS      current
    DESCRIPTION "Constante de calibracion vigente de la humedad."
    ::= { bdlSensorEntrada 8 }

bdlSensorReferenciaTemp OBJECT-TYPE
    SYNTAX      Integer32 (-400..1250)
    UNITS       "decimas de grado C"
    MAX-ACCESS  read-write
    STATUS      current
    DESCRIPTION
        "GET: lectura calibrada actual. SET: valor REAL medido con un
         instrumento de referencia; se recalcula y guarda la constante
         (= POST /calibrar_sensor). inconsistentValue si el sensor no
         mide temperatura."
    ::= { bdlSensorEntrada 9 }

bdlSensorReferenciaHumedad OBJECT-TYPE
    SYNTAX      Integer32 (0..1000)
    UNITS       "decimas de %"
    MAX-ACCESS  read-write
    STATUS      current
    DESCRIPTION
        "Igual que bdlSensorReferenciaTemp, para la humedad.
         inconsistentValue si el sensor no mide humedad."
    ::= { bdlSensorEntrada 10 }

-- =====================================================================
-- .3 energia -- medidor Modbus (RS-485), fases R, S, T
-- =====================================================================

bdlEnergiaTabla OBJECT-TYPE
    SYNTAX      SEQUENCE OF BdlEnergiaEntrada
    MAX-ACCESS  not-accessible
    STATUS      current
    DESCRIPTION
        "Una fila por fase del medidor de energia trifasico. Columnas
         nuevas (potencia, energia...) se agregan al final sin mover
         las existentes."
    ::= { braindlabControlador 3 }

bdlEnergiaEntrada OBJECT-TYPE
    SYNTAX      BdlEnergiaEntrada
    MAX-ACCESS  not-accessible
    STATUS      current
    DESCRIPTION "Una fase."
    INDEX       { bdlEnergiaIndice }
    ::= { bdlEnergiaTabla 1 }

BdlEnergiaEntrada ::= SEQUENCE {
    bdlEnergiaIndice     Integer32,
    bdlEnergiaFase       DisplayString,
    bdlEnergiaEstado     INTEGER,
    bdlEnergiaVoltaje    Integer32,
    bdlEnergiaCorriente  Integer32
}

bdlEnergiaIndice OBJECT-TYPE
    SYNTAX      Integer32 (1..3)
    MAX-ACCESS  not-accessible
    STATUS      current
    DESCRIPTION "1 = R, 2 = S, 3 = T."
    ::= { bdlEnergiaEntrada 1 }

bdlEnergiaFase OBJECT-TYPE
    SYNTAX      DisplayString (SIZE (0..4))
    MAX-ACCESS  read-only
    STATUS      current
    DESCRIPTION "R, S o T."
    ::= { bdlEnergiaEntrada 2 }

bdlEnergiaEstado OBJECT-TYPE
    SYNTAX      INTEGER { ok(1), sinLectura(2) }
    MAX-ACCESS  read-only
    STATUS      current
    DESCRIPTION
        "sinLectura = el medidor no responde; voltaje y corriente son la
         ultima lectura que hubo."
    ::= { bdlEnergiaEntrada 3 }

bdlEnergiaVoltaje OBJECT-TYPE
    SYNTAX      Integer32
    UNITS       "decimas de V"
    MAX-ACCESS  read-only
    STATUS      current
    DESCRIPTION "Voltaje de la fase (2205 = 220.5 V)."
    ::= { bdlEnergiaEntrada 4 }

bdlEnergiaCorriente OBJECT-TYPE
    SYNTAX      Integer32
    UNITS       "centesimas de A"
    MAX-ACCESS  read-only
    STATUS      current
    DESCRIPTION "Corriente de la fase (1234 = 12.34 A)."
    ::= { bdlEnergiaEntrada 5 }

-- =====================================================================
-- .4 sistema
-- =====================================================================

-- .4.1 estado (solo lectura) ------------------------------------------

bdlCicloClimatizacion OBJECT-TYPE
    SYNTAX      INTEGER { reposo(0), normal(1), altaTemperatura(2), bypass(3) }
    MAX-ACCESS  read-only
    STATUS      current
    DESCRIPTION "Etapa actual de la climatizacion."
    ::= { bdlEstado 1 }

bdlTemperaturaMaxima OBJECT-TYPE
    SYNTAX      Integer32
    UNITS       "decimas de grado C"
    MAX-ACCESS  read-only
    STATUS      current
    DESCRIPTION "La mayor de las temperaturas de los sensores 1..4."
    ::= { bdlEstado 2 }

bdlUnidadReserva OBJECT-TYPE
    SYNTAX      Integer32 (1..4)
    MAX-ACCESS  read-only
    STATUS      current
    DESCRIPTION "Aire que descansa esta semana (ver bdlControlReserva)."
    ::= { bdlEstado 3 }

bdlBypassEstadoFisico OBJECT-TYPE
    SYNTAX      INTEGER { inactivo(0), activo(1) }
    MAX-ACCESS  read-only
    STATUS      current
    DESCRIPTION "BPS_STATUS: estado real del bypass leido del hardware."
    ::= { bdlEstado 4 }

bdlBypassAutoHabilitado OBJECT-TYPE
    SYNTAX      INTEGER { no(0), si(1) }
    MAX-ACCESS  read-only
    STATUS      current
    DESCRIPTION "no = se supero fails_max_bypass, el bypass ya no se pide solo."
    ::= { bdlEstado 5 }

bdlRtcOk OBJECT-TYPE
    SYNTAX      INTEGER { falla(0), ok(1) }
    MAX-ACCESS  read-only
    STATUS      current
    DESCRIPTION "Resultado de la ultima lectura del reloj DS1307."
    ::= { bdlEstado 6 }

-- .4.2 mando -- GET = estado REALMENTE aplicado. SET = override manual,
-- igual que desde la web. -----------------------------------------------

bdlModoManual OBJECT-TYPE
    SYNTAX      INTEGER { automatico(0), manual(1) }
    MAX-ACCESS  read-write
    STATUS      current
    DESCRIPTION
        "manual = hay algun override vigente. Escribir automatico(0)
         cancela todos los overrides (= POST /control_automatico).
         Escribir manual(1) devuelve wrongValue: para forzar una salida se
         escribe esa salida."
    ::= { bdlMando 1 }

bdlBypassSolicitado OBJECT-TYPE
    SYNTAX      INTEGER { no(0), si(1) }
    MAX-ACCESS  read-write
    STATUS      current
    DESCRIPTION "Salida BP_S. Confirmar el efecto con bdlBypassEstadoFisico."
    ::= { bdlMando 2 }

bdlBypassManual OBJECT-TYPE
    SYNTAX      INTEGER { no(0), si(1) }
    MAX-ACCESS  read-only
    STATUS      current
    DESCRIPTION "BP_S forzado a mano."
    ::= { bdlMando 3 }

bdlAlarmaAltaTempSalida OBJECT-TYPE
    SYNTAX      INTEGER { inactiva(0), activa(1) }
    MAX-ACCESS  read-write
    STATUS      current
    DESCRIPTION "Salida OUT_AT (contacto seco de alarma)."
    ::= { bdlMando 4 }

bdlAlarmaAltaTempManual OBJECT-TYPE
    SYNTAX      INTEGER { no(0), si(1) }
    MAX-ACCESS  read-only
    STATUS      current
    DESCRIPTION "OUT_AT forzada a mano."
    ::= { bdlMando 5 }

-- .4.3 configuracion -- umbrales EN USO (los cambios desde la web se
-- ven aca despues de reiniciar el equipo) --------------------------------

bdlCantidadAires OBJECT-TYPE
    SYNTAX      Integer32 (1..4)
    MAX-ACCESS  read-only
    STATUS      current
    DESCRIPTION "Cantidad de aires manejados."
    ::= { bdlConfiguracion 1 }

bdlTempMin OBJECT-TYPE
    SYNTAX      Integer32
    UNITS       "decimas de grado C"
    MAX-ACCESS  read-only
    STATUS      current
    DESCRIPTION "Con todos los sensores por debajo de esto se apaga todo."
    ::= { bdlConfiguracion 2 }

bdlTempMax OBJECT-TYPE
    SYNTAX      Integer32
    UNITS       "decimas de grado C"
    MAX-ACCESS  read-only
    STATUS      current
    DESCRIPTION "Activa la etapa normal (N-1 aires)."
    ::= { bdlConfiguracion 3 }

bdlTempAltaTemp OBJECT-TYPE
    SYNTAX      Integer32
    UNITS       "decimas de grado C"
    MAX-ACCESS  read-only
    STATUS      current
    DESCRIPTION "Activa la etapa de alta temperatura (N aires + alarma)."
    ::= { bdlConfiguracion 4 }

bdlTempBypass OBJECT-TYPE
    SYNTAX      Integer32
    UNITS       "decimas de grado C"
    MAX-ACCESS  read-only
    STATUS      current
    DESCRIPTION "Activa el bypass."
    ::= { bdlConfiguracion 5 }

-- .4.4 destinos de trap -- se guardan en config.json y se aplican en
-- caliente. Tambien se editan desde la web (Configuracion > SNMP). ------

bdlTrapDestino1 OBJECT-TYPE
    SYNTAX      IpAddress
    MAX-ACCESS  read-write
    STATUS      current
    DESCRIPTION "IP del gestor 1 (traps a su puerto UDP 162)."
    ::= { bdlTraps 1 }

bdlTrapHabilitado1 OBJECT-TYPE
    SYNTAX      INTEGER { no(0), si(1) }
    MAX-ACCESS  read-write
    STATUS      current
    DESCRIPTION "Habilita los traps hacia bdlTrapDestino1."
    ::= { bdlTraps 2 }

bdlTrapDestino2 OBJECT-TYPE
    SYNTAX      IpAddress
    MAX-ACCESS  read-write
    STATUS      current
    DESCRIPTION "IP del gestor 2."
    ::= { bdlTraps 3 }

bdlTrapHabilitado2 OBJECT-TYPE
    SYNTAX      INTEGER { no(0), si(1) }
    MAX-ACCESS  read-write
    STATUS      current
    DESCRIPTION "Habilita los traps hacia bdlTrapDestino2."
    ::= { bdlTraps 4 }

-- =====================================================================
-- .5 alarmas vigentes (para polling: un trap perdido no se reintenta)
-- =====================================================================

bdlAlarmaAltaTemperatura OBJECT-TYPE
    SYNTAX      INTEGER { normal(0), activa(1) }
    MAX-ACCESS  read-only
    STATUS      current
    DESCRIPTION "Climatizacion en alta temperatura o bypass."
    ::= { bdlAlarmas 1 }

bdlAlarmaBypassActivo OBJECT-TYPE
    SYNTAX      INTEGER { normal(0), activa(1) }
    MAX-ACCESS  read-only
    STATUS      current
    DESCRIPTION "Bypass fisicamente activo (BPS_STATUS)."
    ::= { bdlAlarmas 2 }

bdlAlarmaBypassFalla OBJECT-TYPE
    SYNTAX      INTEGER { normal(0), activa(1) }
    MAX-ACCESS  read-only
    STATUS      current
    DESCRIPTION "BP_S y BPS_STATUS no coinciden hace mas de ~6 s."
    ::= { bdlAlarmas 3 }

bdlAlarmaSensoresTemp OBJECT-TYPE
    SYNTAX      INTEGER { normal(0), activa(1) }
    MAX-ACCESS  read-only
    STATUS      current
    DESCRIPTION
        "Falla de lectura de algun sensor de temperatura 1..4 hace mas de
         ~6 s (ver bdlSensorEstado para saber cual)."
    ::= { bdlAlarmas 4 }

bdlAlarmaSensorGabinete OBJECT-TYPE
    SYNTAX      INTEGER { normal(0), activa(1) }
    MAX-ACCESS  read-only
    STATUS      current
    DESCRIPTION "Sensor 5 (gabinete) sin respuesta hace mas de ~10 s."
    ::= { bdlAlarmas 5 }

bdlAlarmaRtc OBJECT-TYPE
    SYNTAX      INTEGER { normal(0), activa(1) }
    MAX-ACCESS  read-only
    STATUS      current
    DESCRIPTION "DS1307 sin respuesta hace mas de ~6 s."
    ::= { bdlAlarmas 6 }

bdlAlarmaModoManual OBJECT-TYPE
    SYNTAX      INTEGER { normal(0), activa(1) }
    MAX-ACCESS  read-only
    STATUS      current
    DESCRIPTION "Hay algun override manual vigente."
    ::= { bdlAlarmas 7 }

bdlAlarmaBypassAutoDeshabilitado OBJECT-TYPE
    SYNTAX      INTEGER { normal(0), activa(1) }
    MAX-ACCESS  read-only
    STATUS      current
    DESCRIPTION "Se supero fails_max_bypass."
    ::= { bdlAlarmas 8 }

bdlAlarmaMedidorEnergia OBJECT-TYPE
    SYNTAX      INTEGER { normal(0), activa(1) }
    MAX-ACCESS  read-only
    STATUS      current
    DESCRIPTION "Medidor de energia (Modbus) sin lectura hace mas de ~6 s."
    ::= { bdlAlarmas 9 }

-- =====================================================================
-- Notificaciones (traps SNMPv2c, snmpTrapOID = braindlabControlador.0.N)
-- Ademas se envian coldStart (al arrancar) y linkUp (al volver el cable);
-- en ambos casos se reenvian despues las alarmas que sigan activas.
-- Cada alarma tiene un trap de activacion y otro de normalizacion (clear).
-- =====================================================================

bdlTrapAltaTemperatura NOTIFICATION-TYPE
    OBJECTS     { bdlAlarmaAltaTemperatura, bdlCicloClimatizacion, bdlTemperaturaMaxima }
    STATUS      current
    DESCRIPTION "La climatizacion entro en alta temperatura (o bypass)."
    ::= { bdlNotificaciones 1 }

bdlTrapAltaTemperaturaNormal NOTIFICATION-TYPE
    OBJECTS     { bdlAlarmaAltaTemperatura, bdlCicloClimatizacion, bdlTemperaturaMaxima }
    STATUS      current
    DESCRIPTION "La climatizacion salio de alta temperatura. Limpia bdlTrapAltaTemperatura."
    ::= { bdlNotificaciones 2 }

bdlTrapBypassActivado NOTIFICATION-TYPE
    OBJECTS     { bdlAlarmaBypassActivo, bdlBypassSolicitado, bdlBypassEstadoFisico }
    STATUS      current
    DESCRIPTION "El bypass quedo fisicamente activo."
    ::= { bdlNotificaciones 3 }

bdlTrapBypassDesactivado NOTIFICATION-TYPE
    OBJECTS     { bdlAlarmaBypassActivo, bdlBypassSolicitado, bdlBypassEstadoFisico }
    STATUS      current
    DESCRIPTION "El bypass se desactivo. Limpia bdlTrapBypassActivado."
    ::= { bdlNotificaciones 4 }

bdlTrapBypassFalla NOTIFICATION-TYPE
    OBJECTS     { bdlAlarmaBypassFalla, bdlBypassSolicitado, bdlBypassEstadoFisico }
    STATUS      current
    DESCRIPTION "El bypass no obedece: lo pedido (BP_S) no coincide con lo real (BPS_STATUS)."
    ::= { bdlNotificaciones 5 }

bdlTrapBypassFallaNormal NOTIFICATION-TYPE
    OBJECTS     { bdlAlarmaBypassFalla, bdlBypassSolicitado, bdlBypassEstadoFisico }
    STATUS      current
    DESCRIPTION "El bypass volvio a obedecer. Limpia bdlTrapBypassFalla."
    ::= { bdlNotificaciones 6 }

bdlTrapSensoresTempFalla NOTIFICATION-TYPE
    OBJECTS     { bdlAlarmaSensoresTemp }
    STATUS      current
    DESCRIPTION "Falla de lectura de algun sensor de temperatura 1..4."
    ::= { bdlNotificaciones 7 }

bdlTrapSensoresTempNormal NOTIFICATION-TYPE
    OBJECTS     { bdlAlarmaSensoresTemp }
    STATUS      current
    DESCRIPTION "Los sensores 1..4 volvieron a leer bien. Limpia bdlTrapSensoresTempFalla."
    ::= { bdlNotificaciones 8 }

bdlTrapSensorGabineteFalla NOTIFICATION-TYPE
    OBJECTS     { bdlAlarmaSensorGabinete, bdlSensorTemperatura }
    STATUS      current
    DESCRIPTION "Sensor 5 (gabinete) sin respuesta. Trae su ultima temperatura buena."
    ::= { bdlNotificaciones 9 }

bdlTrapSensorGabineteNormal NOTIFICATION-TYPE
    OBJECTS     { bdlAlarmaSensorGabinete, bdlSensorTemperatura }
    STATUS      current
    DESCRIPTION "Sensor 5 (gabinete) volvio a responder. Limpia bdlTrapSensorGabineteFalla."
    ::= { bdlNotificaciones 10 }

bdlTrapRtcFalla NOTIFICATION-TYPE
    OBJECTS     { bdlAlarmaRtc }
    STATUS      current
    DESCRIPTION "DS1307 sin respuesta."
    ::= { bdlNotificaciones 11 }

bdlTrapRtcNormal NOTIFICATION-TYPE
    OBJECTS     { bdlAlarmaRtc }
    STATUS      current
    DESCRIPTION "DS1307 volvio a responder. Limpia bdlTrapRtcFalla."
    ::= { bdlNotificaciones 12 }

bdlTrapModoManualActivado NOTIFICATION-TYPE
    OBJECTS     { bdlAlarmaModoManual }
    STATUS      current
    DESCRIPTION "Alguien forzo una salida a mano (web, pantalla o SNMP)."
    ::= { bdlNotificaciones 13 }

bdlTrapModoManualDesactivado NOTIFICATION-TYPE
    OBJECTS     { bdlAlarmaModoManual }
    STATUS      current
    DESCRIPTION "La automatica retomo el control de todo. Limpia bdlTrapModoManualActivado."
    ::= { bdlNotificaciones 14 }

bdlTrapBypassAutoDeshabilitado NOTIFICATION-TYPE
    OBJECTS     { bdlAlarmaBypassAutoDeshabilitado }
    STATUS      current
    DESCRIPTION "Se supero fails_max_bypass: el bypass ya no se pide solo."
    ::= { bdlNotificaciones 15 }

bdlTrapCalibracionModificada NOTIFICATION-TYPE
    STATUS      current
    DESCRIPTION
        "Cambio una constante de calibracion. El unico varbind es la
         constante nueva: bdlSensorCalibTemperatura o
         bdlSensorCalibHumedad del sensor que se calibro."
    ::= { bdlNotificaciones 16 }

bdlTrapPrueba NOTIFICATION-TYPE
    OBJECTS     { bdlCicloClimatizacion, bdlTemperaturaMaxima }
    STATUS      current
    DESCRIPTION
        "Trap de prueba enviado a mano desde la web (Configuracion > SNMP)
         para verificar que el gestor recibe. No indica ninguna alarma."
    ::= { bdlNotificaciones 17 }

bdlTrapMedidorEnergiaFalla NOTIFICATION-TYPE
    OBJECTS     { bdlAlarmaMedidorEnergia }
    STATUS      current
    DESCRIPTION "El medidor de energia (Modbus) dejo de responder."
    ::= { bdlNotificaciones 18 }

bdlTrapMedidorEnergiaNormal NOTIFICATION-TYPE
    OBJECTS     { bdlAlarmaMedidorEnergia }
    STATUS      current
    DESCRIPTION "El medidor de energia volvio a responder. Limpia bdlTrapMedidorEnergiaFalla."
    ::= { bdlNotificaciones 19 }

END
